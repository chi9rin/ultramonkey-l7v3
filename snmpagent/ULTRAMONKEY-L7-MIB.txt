ULTRAMONKEY-L7-MIB DEFINITIONS ::= BEGIN
IMPORTS
    MODULE-IDENTITY, OBJECT-TYPE, NOTIFICATION-TYPE, enterprises,
        FROM SNMPv2-SMI
    DisplayString
        FROM SNMPv2-TC
    InetAddress, InetPortNumber
        FROM INET-ADDRESS-MIB
;

ultramonkey-l7 MODULE-IDENTITY
    LAST-UPDATED "0810040000Z"
    ORGANIZATION "NTT COMWARE"
    CONTACT-INFO
    "UltraMonkey-L7 Community
     URL: http://sourceforge.jp/projects/ultramonkey-l7/"
    DESCRIPTION
    "A MIB module for UltraMonkey-L7"
    ::= { enterprises 60000 }

um7Traps    OBJECT IDENTIFIER ::= { ultramonkey-l7 0 }
um7Objects  OBJECT IDENTIFIER ::= { ultramonkey-l7 1 }

-- Current Data Group

um7CurrentDataGroup  OBJECT IDENTIFIER ::= { um7Objects 1 }

    um7VirtualServiceTable OBJECT-TYPE
        SYNTAX      SEQUENCE OF Um7VirtualServiceEntry
        MAX-ACCESS  not-accessible
        STATUS      current
        DESCRIPTION
        "The table of Virtual Service data."
        ::= { um7CurrentDataGroup 1 }
   
    um7VirtualServiceEntry OBJECT-TYPE
        SYNTAX     Um7VirtualServiceEntry
        MAX-ACCESS not-accessible
        STATUS     current
        DESCRIPTION
        "The information about one Virtual Service data."
        INDEX { um7VSIndex }
        ::= { um7VirtualServiceTable 1 }
   
    Um7VirtualServiceEntry ::= SEQUENCE {
        um7VSIndex              INTEGER (1..127),
        um7VSProtocol           INTEGER { tcp(1), udp(2) },
        um7VSIPAddress          InetAddress,
        um7VSPortNumber         InetPortNumber,
        um7VSScheduleModule     DisplayString,
        um7VSProtocolModule     DisplayString,
        um7VSProtoModOption     DisplayString,
        um7VSReschedule         INTEGER { on(1), off(2) },
        um7VSSorryIpAddress     InetAddress,
        um7VSSorryPortNumber    InetPortNumber,
        um7VSSorryThreshold     INTEGER (0..2147483647),
        um7VSSorryForceFlag     INTEGER { on(1), off(2) },
        um7VSQoSThresholdUp     INTEGER (0..18446744073709551615),
        um7VSQoSThresholdDown   INTEGER (0..18446744073709551615),
        um7VSThroughputUp       INTEGER (0..18446744073709551615),
        um7VSThroughputDown     INTEGER (0..18446744073709551615)
    }
   
    um7VSIndex OBJECT-TYPE
        SYNTAX      INTEGER (1..127)
        MAX-ACCESS  not-accessible
        STATUS      current
        DESCRIPTION
        "The data index of Virtual Service."
        ::= { um7VirtualServiceEntry 1 }

    um7VSProtocol OBJECT-TYPE
        SYNTAX      INTEGER {
                        tcp(1),
                        udp(2)
                    }
        MAX-ACCESS read-only
        STATUS     current
        DESCRIPTION
        "Protocol id of Virtual Service."
        ::= { um7VirtualServiceEntry 2 }

    um7VSIPAddress  OBJECT-TYPE
        SYNTAX      InetAddress
        MAX-ACCESS  read-only
        STATUS      current
        DESCRIPTION
        "IP address of Virtual Service."
        ::= { um7VirtualServiceEntry 3 }

    um7VSPortNumber OBJECT-TYPE
        SYNTAX      InetPortNumber
        MAX-ACCESS  read-only
        STATUS      current
        DESCRIPTION
        "Port number of Virtual Service."
        ::= { um7VirtualServiceEntry 4 }

    um7VSScheduleModule OBJECT-TYPE
        SYNTAX      DisplayString
        MAX-ACCESS  read-only
        STATUS      current
        DESCRIPTION
        "Schedule module of Virtual Service."
        ::= { um7VirtualServiceEntry 5 }

    um7VSProtocolModule OBJECT-TYPE
        SYNTAX      DisplayString
        MAX-ACCESS  read-only
        STATUS      current
        DESCRIPTION
        "Protocol module of Virtual Service."
        ::= { um7VirtualServiceEntry 6 }

    um7VSProtocolModuleOption OBJECT-TYPE
        SYNTAX      DisplayString
        MAX-ACCESS  read-only
        STATUS      current
        DESCRIPTION
        "Protocol module option of Virtual Service."
        ::= { um7VirtualServiceEntry 7 }

    um7VSReschedule OBJECT-TYPE
        SYNTAX      INTEGER {
                        on(1),
                        off(2)
                    }
        MAX-ACCESS  read-only
        STATUS      current
        DESCRIPTION
        "Protocol module reschedule flag of Virtual Service."
        ::= { um7VirtualServiceEntry 8 }

    um7VSSorryIpAddress OBJECT-TYPE
        SYNTAX      InetAddress
        MAX-ACCESS  read-only
        STATUS      current
        DESCRIPTION
        "IP address of sorry server."
        ::= { um7VirtualServiceEntry 9 }

    um7VSSorryPortNumber OBJECT-TYPE
        SYNTAX      InetPortNumber
        MAX-ACCESS  read-only
        STATUS      current
        DESCRIPTION
        "Port number of sorry server."
        ::= { um7VirtualServiceEntry 10 }

    um7VSSorryThreshold OBJECT-TYPE
        SYNTAX      INTEGER (0..2147483647)
        UNITS        "Connections"
        MAX-ACCESS  read-only
        STATUS      current
        DESCRIPTION
        "Connection threshold of sorry server."
        ::= { um7VirtualServiceEntry 11 }

    um7VSSorryForceFlag OBJECT-TYPE
        SYNTAX      INTEGER {
                        on(1),
                        off(2)
                    }
        MAX-ACCESS  read-only
        STATUS      current
        DESCRIPTION
        "Force flag of sorry server."
        ::= { um7VirtualServiceEntry 12 }

    um7VSQoSThresholdUp OBJECT-TYPE
        SYNTAX      INTEGER (0..18446744073709551615)
        UNITS        "bps"
        MAX-ACCESS  read-only
        STATUS      current
        DESCRIPTION
        "QoS threshold of up stream."
        ::= { um7VirtualServiceEntry 13 }

    um7VSQoSThresholdDown OBJECT-TYPE
        SYNTAX      INTEGER (0..18446744073709551615)
        UNITS        "bps"
        MAX-ACCESS  read-only
        STATUS      current
        DESCRIPTION
        "QoS threshold of down stream."
        ::= { um7VirtualServiceEntry 14 }

    um7VSThroughputUp OBJECT-TYPE
        SYNTAX      INTEGER (0..18446744073709551615)
        UNITS        "bps"
        MAX-ACCESS  read-only
        STATUS      current
        DESCRIPTION
        "Current throughput of up stream."
        ::= { um7VirtualServiceEntry 15 }

    um7VSThroughputDown OBJECT-TYPE
        SYNTAX      INTEGER (0..18446744073709551615)
        UNITS        "bps"
        MAX-ACCESS  read-only
        STATUS      current
        DESCRIPTION
        "Current throughput of down stream."
        ::= { um7VirtualServiceEntry 16 }

    um7RealServerTable OBJECT-TYPE
        SYNTAX      SEQUENCE OF Um7RealServerEntry
        MAX-ACCESS  not-accessible
        STATUS      current
        DESCRIPTION
        "The table of Real Server data."
        ::= { um7CurrentDataGroup 2 }
   
    um7RealServerEntry OBJECT-TYPE
        SYNTAX     Um7RealServerEntry
        MAX-ACCESS not-accessible
        STATUS     current
        DESCRIPTION
        "The information about one Real Server data."
        INDEX { um7RSIndex }
        ::= { um7RealServerTable 1 }
   
    Um7RealServerEntry ::= SEQUENCE {
        um7RSIndex                  INTEGER (1..65535)
        um7RSVirtualServiceIndex    INTEGER (1..127)
        um7RSIPAddress              InetAddress
        um7RSPortNumber             InetPortNumber
        um7RSForwardMode            INTEGER { masq(1) }
        um7RSWeight                 INTEGER (0..2147483647)
        um7RSActiveConn             INTEGER (0..2147483647)
        um7RSInactiveConn           INTEGER (0..2147483647)
    }
   
    um7RSIndex OBJECT-TYPE
        SYNTAX      INTEGER (1..65535)
        MAX-ACCESS  not-accessible
        STATUS      current
        DESCRIPTION
        "The data index of Real Server."
        ::= { um7RealServerEntry 1 }

    um7RSVirtualServiceIndex OBJECT-TYPE
        SYNTAX      INTEGER(1..127)
        MAX-ACCESS  read-only
        STATUS      current
        DESCRIPTION
        "Virtual Service index of Real Server."
        ::= { um7RealServerEntry 2 }

    um7RSIPAddress OBJECT-TYPE
        SYNTAX      InetAddress
        MAX-ACCESS  read-only
        STATUS      current
        DESCRIPTION
        "IP address of Real Server."
        ::= { um7RealServerEntry 3 }

    um7RSPortNumber OBJECT-TYPE
        SYNTAX      InetPortNumber
        MAX-ACCESS  read-only
        STATUS      current
        DESCRIPTION
        "Port number of Real Server."
        ::= { um7RealServerEntry 4 }

    um7RSForwardMode OBJECT-TYPE
        SYNTAX      INTEGER { masq(1) }
        MAX-ACCESS  read-only
        STATUS      current
        DESCRIPTION
        "Forward mode of Real Server."
        ::= { um7RealServerEntry 5 }

    um7RSWeight OBJECT-TYPE
        SYNTAX      INTEGER (0..2147483647)
        MAX-ACCESS  read-only
        STATUS      current
        DESCRIPTION
        "Weight of Real Server."
        ::= { um7RealServerEntry 6 }

    um7RSActiveConn OBJECT-TYPE
        SYNTAX      INTEGER (0..2147483647)
        MAX-ACCESS  read-only
        STATUS      current
        DESCRIPTION
        "Active connections of Real Server."
        ::= { um7RealServerEntry 7 }

    um7RSInactiveConn OBJECT-TYPE
        SYNTAX      INTEGER (0..2147483647)
        MAX-ACCESS  read-only
        STATUS      current
        DESCRIPTION
        "Inactive connections of Real Server."
        ::= { um7RealServerEntry 8 }

um7LogLevel             OBJECT IDENTIFIER ::= { um7CurrentDataGroup 3 }
um7LogLevelL7vsd        OBJECT IDENTIFIER ::= { um7LogLevel 1 }
um7LogLevelL7vsadm      OBJECT IDENTIFIER ::= { um7LogLevel 2 }
um7LogLevelSnmpAgent    OBJECT IDENTIFIER ::= { um7LogLevel 3 }

Um7LogLevel ::= INTEGER {
    unknown(0),
    debug(1),
    info(2),
    warn(3),
    error(4),
    fatal(5)
}

    um7LogVsdNetwork OBJECT-TYPE
        SYNTAX      Um7LogLevel
        MAX-ACCESS  read-only
        STATUS      current
        DESCRIPTION
        "Log Level of l7vsd network."
        ::= { um7LogLevelL7vsd 1 }

    um7LogVsdNetworkBandwidth OBJECT-TYPE
        SYNTAX      Um7LogLevel
        MAX-ACCESS  read-only
        STATUS      current
        DESCRIPTION
        "Log Level of l7vsd network bandwidth."
        ::= { um7LogLevelL7vsd 2 }

    um7LogVsdNetworkNumConnection OBJECT-TYPE
        SYNTAX      Um7LogLevel
        MAX-ACCESS  read-only
        STATUS      current
        DESCRIPTION
        "Log Level of l7vsd network num connection."
        ::= { um7LogLevelL7vsd 3 }

    um7LogVsdNetworkQoS OBJECT-TYPE
        SYNTAX      Um7LogLevel
        MAX-ACCESS  read-only
        STATUS      current
        DESCRIPTION
        "Log Level of l7vsd network QoS."
        ::= { um7LogLevelL7vsd 4 }

    um7LogVsdVirtualService OBJECT-TYPE
        SYNTAX      Um7LogLevel
        MAX-ACCESS  read-only
        STATUS      current
        DESCRIPTION
        "Log Level of l7vsd Virtual Service."
        ::= { um7LogLevelL7vsd 5 }

    um7LogVsdRealServer OBJECT-TYPE
        SYNTAX      Um7LogLevel
        MAX-ACCESS  read-only
        STATUS      current
        DESCRIPTION
        "Log Level of l7vsd Real Server."
        ::= { um7LogLevelL7vsd 6 }

    um7LogVsdRealServerBalancing OBJECT-TYPE
        SYNTAX      Um7LogLevel
        MAX-ACCESS  read-only
        STATUS      current
        DESCRIPTION
        "Log Level of l7vsd Real Server balancing."
        ::= { um7LogLevelL7vsd 7 }

    um7LogVsdSorryServer OBJECT-TYPE
        SYNTAX      Um7LogLevel
        MAX-ACCESS  read-only
        STATUS      current
        DESCRIPTION
        "Log Level of l7vsd Sorry Server."
        ::= { um7LogLevelL7vsd 8 }

    um7LogVsdReplication OBJECT-TYPE
        SYNTAX      Um7LogLevel
        MAX-ACCESS  read-only
        STATUS      current
        DESCRIPTION
        "Log Level of l7vsd replication."
        ::= { um7LogLevelL7vsd 9 }

    um7LogVsdStartStop OBJECT-TYPE
        SYNTAX      Um7LogLevel
        MAX-ACCESS  read-only
        STATUS      current
        DESCRIPTION
        "Log Level of l7vsd start stop."
        ::= { um7LogLevelL7vsd 10 }

    um7LogVsdSystem OBJECT-TYPE
        SYNTAX      Um7LogLevel
        MAX-ACCESS  read-only
        STATUS      current
        DESCRIPTION
        "Log Level of l7vsd system."
        ::= { um7LogLevelL7vsd 11 }

    um7LogVsdSystemMemory OBJECT-TYPE
        SYNTAX      Um7LogLevel
        MAX-ACCESS  read-only
        STATUS      current
        DESCRIPTION
        "Log Level of l7vsd system memory."
        ::= { um7LogLevelL7vsd 12 }

    um7LogVsdSystemSocket OBJECT-TYPE
        SYNTAX      Um7LogLevel
        MAX-ACCESS  read-only
        STATUS      current
        DESCRIPTION
        "Log Level of l7vsd system socket."
        ::= { um7LogLevelL7vsd 13 }

    um7LogVsdSystemSignal OBJECT-TYPE
        SYNTAX      Um7LogLevel
        MAX-ACCESS  read-only
        STATUS      current
        DESCRIPTION
        "Log Level of l7vsd system signal."
        ::= { um7LogLevelL7vsd 14 }

    um7LogVsdEnvironment OBJECT-TYPE
        SYNTAX      Um7LogLevel
        MAX-ACCESS  read-only
        STATUS      current
        DESCRIPTION
        "Log Level of l7vsd environment."
        ::= { um7LogLevelL7vsd 15 }

    um7LogVsdEnvironmentParameter OBJECT-TYPE
        SYNTAX      Um7LogLevel
        MAX-ACCESS  read-only
        STATUS      current
        DESCRIPTION
        "Log Level of l7vsd environment parameter."
        ::= { um7LogLevelL7vsd 16 }

    um7LogVsdLogger OBJECT-TYPE
        SYNTAX      Um7LogLevel
        MAX-ACCESS  read-only
        STATUS      current
        DESCRIPTION
        "Log Level of l7vsd logger."
        ::= { um7LogLevelL7vsd 17 }

    um7LogVsdParameter OBJECT-TYPE
        SYNTAX      Um7LogLevel
        MAX-ACCESS  read-only
        STATUS      current
        DESCRIPTION
        "Log Level of l7vsd parameter."
        ::= { um7LogLevelL7vsd 18 }

    um7LogVsdEvent OBJECT-TYPE
        SYNTAX      Um7LogLevel
        MAX-ACCESS  read-only
        STATUS      current
        DESCRIPTION
        "Log Level of l7vsd event."
        ::= { um7LogLevelL7vsd 19 }

    um7LogVsdSchedule OBJECT-TYPE
        SYNTAX      Um7LogLevel
        MAX-ACCESS  read-only
        STATUS      current
        DESCRIPTION
        "Log Level of l7vsd schedule."
        ::= { um7LogLevelL7vsd 20 }

    um7LogVsdProgram OBJECT-TYPE
        SYNTAX      Um7LogLevel
        MAX-ACCESS  read-only
        STATUS      current
        DESCRIPTION
        "Log Level of l7vsd program."
        ::= { um7LogLevelL7vsd 21 }

    um7LogVsdProtocol OBJECT-TYPE
        SYNTAX      Um7LogLevel
        MAX-ACCESS  read-only
        STATUS      current
        DESCRIPTION
        "Log Level of l7vsd protocol."
        ::= { um7LogLevelL7vsd 22 }

    um7LogVsdModule OBJECT-TYPE
        SYNTAX      Um7LogLevel
        MAX-ACCESS  read-only
        STATUS      current
        DESCRIPTION
        "Log Level of l7vsd module."
        ::= { um7LogLevelL7vsd 23 }

    um7LogVsadmParse OBJECT-TYPE
        SYNTAX      Um7LogLevel
        MAX-ACCESS  read-only
        STATUS      current
        DESCRIPTION
        "Log Level of l7vsadm parse."
        ::= { um7LogLevelL7vsadm 1 }

    um7LogVsadmOperate OBJECT-TYPE
        SYNTAX      Um7LogLevel
        MAX-ACCESS  read-only
        STATUS      current
        DESCRIPTION
        "Log Level of l7vsadm operate."
        ::= { um7LogLevelL7vsadm 2 }

    um7LogVsadmCommunicate OBJECT-TYPE
        SYNTAX      Um7LogLevel
        MAX-ACCESS  read-only
        STATUS      current
        DESCRIPTION
        "Log Level of l7vsadm communicate."
        ::= { um7LogLevelL7vsadm 3 }

    um7LogVsadmConfigResult OBJECT-TYPE
        SYNTAX      Um7LogLevel
        MAX-ACCESS  read-only
        STATUS      current
        DESCRIPTION
        "Log Level of l7vsadm config result."
        ::= { um7LogLevelL7vsadm 4 }

    um7LogVsadmCommon OBJECT-TYPE
        SYNTAX      Um7LogLevel
        MAX-ACCESS  read-only
        STATUS      current
        DESCRIPTION
        "Log Level of l7vsadm common."
        ::= { um7LogLevelL7vsadm 5 }

    um7LogVsadmLogger OBJECT-TYPE
        SYNTAX      Um7LogLevel
        MAX-ACCESS  read-only
        STATUS      current
        DESCRIPTION
        "Log Level of l7vsadm logger."
        ::= { um7LogLevelL7vsadm 6 }

    um7LogVsadmParameter OBJECT-TYPE
        SYNTAX      Um7LogLevel
        MAX-ACCESS  read-only
        STATUS      current
        DESCRIPTION
        "Log Level of l7vsadm parameter."
        ::= { um7LogLevelL7vsadm 7 }

    um7LogVsadmProtocol OBJECT-TYPE
        SYNTAX      Um7LogLevel
        MAX-ACCESS  read-only
        STATUS      current
        DESCRIPTION
        "Log Level of l7vsadm protocol."
        ::= { um7LogLevelL7vsadm 8 }

    um7LogVsadmModule OBJECT-TYPE
        SYNTAX      Um7LogLevel
        MAX-ACCESS  read-only
        STATUS      current
        DESCRIPTION
        "Log Level of l7vsadm module."
        ::= { um7LogLevelL7vsadm 9 }

    um7LogSnmpStartStop OBJECT-TYPE
        SYNTAX      Um7LogLevel
        MAX-ACCESS  read-only
        STATUS      current
        DESCRIPTION
        "Log Level of l7snmpagent start stop."
        ::= { um7LogLevelSnmpAgent 1 }

    um7LogSnmpManagerReceive OBJECT-TYPE
        SYNTAX      Um7LogLevel
        MAX-ACCESS  read-only
        STATUS      current
        DESCRIPTION
        "Log Level of l7snmpagent manager-receive."
        ::= { um7LogLevelSnmpAgent 2 }

    um7LogSnmpManagerSend OBJECT-TYPE
        SYNTAX      Um7LogLevel
        MAX-ACCESS  read-only
        STATUS      current
        DESCRIPTION
        "Log Level of l7snmpagent manager-send."
        ::= { um7LogLevelSnmpAgent 3 }

    um7LogSnmpL7vsdReceive OBJECT-TYPE
        SYNTAX      Um7LogLevel
        MAX-ACCESS  read-only
        STATUS      current
        DESCRIPTION
        "Log Level of l7snmpagent l7vsd-receive"
        ::= { um7LogLevelSnmpAgent 4 }

    um7LogSnmpL7vsdSend OBJECT-TYPE
        SYNTAX      Um7LogLevel
        MAX-ACCESS  read-only
        STATUS      current
        DESCRIPTION
        "Log Level of l7snmpagent l7vsd-send"
        ::= { um7LogLevelSnmpAgent 5 }

    um7LogSnmpLogger OBJECT-TYPE
        SYNTAX      Um7LogLevel
        MAX-ACCESS  read-only
        STATUS      current
        DESCRIPTION
        "Log Level of l7snmpagent logger"
        ::= { um7LogLevelSnmpAgent 6 }

    um7LogSnmpParameter OBJECT-TYPE
        SYNTAX      Um7LogLevel
        MAX-ACCESS  read-only
        STATUS      current
        DESCRIPTION
        "Log Level of l7snmpagent parameter"
        ::= { um7LogLevelSnmpAgent 7 }

um7Status       OBJECT IDENTIFIER ::= { um7CurrentDataGroup 4 }

    um7StatMessage OBJECT-TYPE
        SYNTAX      DisplayString
        MAX-ACCESS  read-only
        STATUS      current
        DESCRIPTION
        "Status message of l7vsd."
        ::= { um7Status 1 }

    um7StatReplication OBJECT-TYPE
        SYNTAX      INTEGER {
                        out(1),
                        single(2),
                        master(3),
                        slave(4),
                        masterstop(5),
                        slavestop(6)
                    }
        MAX-ACCESS  read-only
        STATUS      current
        DESCRIPTION
        "Status of replication."
        ::= { um7Status 2 }

    um7StatSnmpAgent OBJECT-TYPE
        SYNTAX      INTEGER {
                        unknown(0),
                        disconnect(1),
                        connect(2)
                    }
        MAX-ACCESS  read-only
        STATUS      current
        DESCRIPTION
        "Status of l7snmpagent."
        ::= { um7Status 3 }

-- Traps

    um7StateAlert  NOTIFICATION-TYPE
        OBJECTS { um7StatSnmpAgent, um7StatReplication }  
        STATUS  current
        DESCRIPTION
        "Trap of process status change."
        ::= { um7Traps 1 }

    um7VirtualServiceAlert  NOTIFICATION-TYPE
        OBJECTS { um7VirtualServiceTable, um7RealServerTable }  
        STATUS  current
        DESCRIPTION
        "Trap of Virtual Service change."
        ::= { um7Traps 2 }

    um7ReplicationAlert  NOTIFICATION-TYPE
        OBJECTS { um7StatMessage }
        STATUS  current
        DESCRIPTION
        "Trap of replication command execution."
        ::= { um7Traps 3 }

    um7LogLevelAlert  NOTIFICATION-TYPE
        OBJECTS { um7LogLevel }  
        STATUS  current
        DESCRIPTION
        "Trap of log level change."
        ::= { um7Traps 4 }

    um7QoSAlarmOn  NOTIFICATION-TYPE
        OBJECTS { um7VSQoSThresholdUp, um7VSQoSThresholdDown, um7VSThroughputUp, um7VSThroughputDown }
        STATUS  current
        DESCRIPTION
        "Trap of throughput over QoS threshold."
        ::= { um7Traps 5 }

    um7QoSAlarmOff  NOTIFICATION-TYPE
        OBJECTS { um7VSQoSThresholdUp, um7VSQoSThresholdDown, um7VSThroughputUp, um7VSThroughputDown }
        STATUS  current
        DESCRIPTION
        "Trap of throughput under QoS threshold."
        ::= { um7Traps 6 }

    um7MessageAlert  NOTIFICATION-TYPE
        OBJECTS { um7StatMessage }
        STATUS  current
        DESCRIPTION
        "Trap of some message."
        ::= { um7Traps 7 }


-- conformance information

um7MIBConformance OBJECT IDENTIFIER ::= { ultramonkey-l7 2 }
um7MIBCompliances OBJECT IDENTIFIER ::= { um7MIBConformance 1 }
um7MIBGroups      OBJECT IDENTIFIER ::= { um7MIBConformance 2 }


-- compliance statements

um7MIBCompliance MODULE-COMPLIANCE
    STATUS  current
    DESCRIPTION
    "The compliance statement for UltraMonkey-L7."
    MODULE  -- this module

    MANDATORY-GROUPS { um7MIBGroup, um7TrapGroup }
    ::= { um7MIBCompliances 1 }

-- units of conformance

um7MIBGroup OBJECT-GROUP
    OBJECTS   { um7VSIndex, um7VSProtocol, um7VSIPAddress, 
                um7VSPortNumber, um7VSScheduleModule, um7VSProtocolModule,
                um7VSProtocolModuleOption, um7VSReschedule, um7VSSorryIpAddress,
                um7VSSorryThreshold, um7VSSorryForceFlag, um7VSQoSThresholdUp,
                um7VSQoSThresholdDown, um7VSThroughputUp, um7VSThroughputDown,
                um7RSIndex, um7RSVirtualServiceIndex, um7RSIPAddress,
                um7RSPortNumber, um7RSForwardMode, um7RSWeight,
                um7RSActiveConn, um7RSInactiveConn, um7LogVsdNetwork,
                um7LogVsdNetworkBandwidth, um7LogVsdNetworkNumConnection,
                um7LogVsdNetworkQoS, um7LogVsdVirtualService,
                um7LogVsdRealServer, um7LogVsdRealServerBalancing,
                um7LogVsdSorryServer, um7LogVsdReplication,
                um7LogVsdStartStop, um7LogVsdSystem, um7LogVsdSystemMemory,
                um7LogVsdSystemSocket, um7LogVsdSystemSignal,
                um7LogVsdEnvironment, um7LogVsdEnvironmentParameter,
                um7LogVsdLogger, um7LogVsdParameter, um7LogVsdEvent,
                um7LogVsdSchedule, um7LogVsdProgram, um7LogVsdProtocol,
                um7LogVsdModule, um7LogVsadmParse, um7LogVsadmOperate,
                um7LogVsadmCommunicate, um7LogVsadmConfigResult,
                um7LogVsadmCommon, um7LogVsadmLogger, um7LogVsadmParameter,
                um7LogVsadmProtocol, um7LogVsadmModule, um7LogSnmpStartStop,
                um7LogSnmpManagerReceive, um7LogSnmpManagerSend,
                um7LogSnmpL7vsdReceive, um7LogSnmpL7vsdSend,
                um7LogSnmpLogger, um7LogSnmpParameter, um7StatSnmpAgent,
                um7StatReplication }
    STATUS    current
    DESCRIPTION
    "The MIB group of objects providing for management of UltraMonkey-L7."
    ::= { um7MIBGroups 1 }

um7TrapGroup NOTIFICATION-GROUP
    NOTIFICATIONS { um7StateAlert, um7VirtualServiceAlert,
                    um7ReplicationAlert, um7LogLevelAlert,
                    um7QoSAlarmOn, um7QoSAlarmOff,
                    um7MessageAlert }
    STATUS  current
    DESCRIPTION
    "The notifications group for UltraMonkey-L7."
    ::= { um7MIBGroups 2 }

END
